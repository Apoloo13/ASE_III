Attribute VB_Name = "control_general1"
Option Explicit


Public Sub CATMain()

    Dim CatSys As Variant
    Dim parametros() As Variant

    Dim rutaLengua As String


    ' ========================================================
    ' OBTENER SYSTEMSERVICE MEDIANTE LATE BINDING
    ' ========================================================

    Set CatSys = CATIA.SystemService


    ' ========================================================
    ' RUTA DEL CONTROL DE LA LENGUA
    ' ========================================================

    rutaLengua = _
        "C:\Users\Apolinar\Desktop\mano derecha\github\ASE_III\diseño_3d\mecanismos\macros\VBA\control_lengua.catvba"


    ' ========================================================
    ' EJECUTAR CONTROL DE LENGUA
    '
    ' El numero 2 significa:
    ' catScriptLibraryTypeVBAProject
    '
    ' Lo ponemos como numero para evitar tambien problemas
    ' de tipos/enumeraciones de CATIA en VBA.
    ' ========================================================

    On Error GoTo ErrorLengua


    Call CatSys.ExecuteScript( _
        rutaLengua, _
        2, _
        "Module1", _
        "CATMain", _
        parametros)


    Exit Sub


' ============================================================
' ERROR
' ============================================================

ErrorLengua:

    MsgBox _
        "No pude abrir el control de la lengua." & vbCrLf & vbCrLf & _
        "Error " & Err.Number & vbCrLf & _
        Err.Description, _
        vbCritical, _
        "Control general"

End Sub
