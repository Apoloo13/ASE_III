Attribute VB_Name = "Module1"
Option Explicit


' ============================================================
' CONTROL MANUAL DE LENGUA
' CATIA V5 - DMU KINEMATICS
' ============================================================


' ============================================================
' VARIABLES GLOBALES
' ============================================================

Public gMechanism As Variant

Public gValores() As Variant

' gQV = movimiento vertical REAL
'       positivo = ARRIBA
'
' gQH = movimiento horizontal REAL
'       positivo = DERECHA

Public gQV As Double
Public gQH As Double


' ============================================================
' LIMITES
' ============================================================

Public Const LIMITE_V As Double = 8#
Public Const LIMITE_H As Double = 8#


' ============================================================
' COMMANDS
'
' Estos nombres V/H son los que habiamos supuesto inicialmente.
'
' Pero por la orientacion REAL de tu modelo:
'
' CMD_H controla fisicamente ARRIBA / ABAJO
'
' CMD_V controla fisicamente IZQUIERDA / DERECHA
' y ademas tiene el signo invertido.
'
' ============================================================

Public Const CMD_V1 As Integer = 1
Public Const CMD_H1 As Integer = 2

Public Const CMD_V2 As Integer = 3
Public Const CMD_H2 As Integer = 4

Public Const CMD_V3 As Integer = 5
Public Const CMD_H3 As Integer = 6

Public Const CMD_V4 As Integer = 7
Public Const CMD_H4 As Integer = 8


' ============================================================
' CATMAIN
' ============================================================

Public Sub CATMain()

    Dim doc As Object
    Dim rootProduct As Object
    Dim mechanisms As Object

    Dim nComandos As Long


    ' --------------------------------------------------------
    ' Comprobar documento
    ' --------------------------------------------------------

    If CATIA.Documents.Count = 0 Then

        MsgBox _
            "No hay ningun documento abierto.", _
            vbExclamation, _
            "Control de lengua"

        Exit Sub

    End If


    Set doc = CATIA.ActiveDocument


    If TypeName(doc) <> "ProductDocument" Then

        MsgBox _
            "Debes tener abierto el CATProduct de la lengua.", _
            vbExclamation, _
            "Control de lengua"

        Exit Sub

    End If


    ' --------------------------------------------------------
    ' Producto principal
    ' --------------------------------------------------------

    Set rootProduct = doc.Product


    ' --------------------------------------------------------
    ' Obtener mecanismos
    ' --------------------------------------------------------

    On Error GoTo ErrorMecanismo

    Set mechanisms = _
        rootProduct.GetTechnologicalObject("Mechanisms")

    On Error GoTo 0


    If mechanisms.Count = 0 Then

        MsgBox _
            "No se encontro ningun mecanismo.", _
            vbCritical, _
            "Control de lengua"

        Exit Sub

    End If


    ' --------------------------------------------------------
    ' Mechanism.1
    ' --------------------------------------------------------

    Set gMechanism = mechanisms.Item(1)


    ' --------------------------------------------------------
    ' Numero de comandos
    ' --------------------------------------------------------

    nComandos = gMechanism.NbCommands


    If nComandos <> 14 Then

        MsgBox _
            "CATIA encontro " & nComandos & _
            " comandos." & vbCrLf & vbCrLf & _
            "Esta macro esta configurada para 14 comandos.", _
            vbCritical, _
            "Control de lengua"

        Exit Sub

    End If


    ' --------------------------------------------------------
    ' Crear array
    ' --------------------------------------------------------

    ReDim gValores(0 To nComandos - 1)


    ' --------------------------------------------------------
    ' Leer posicion actual
    ' --------------------------------------------------------

    On Error GoTo ErrorLectura

    Call gMechanism.GetCommandValues(gValores)

    On Error GoTo 0


    ' ========================================================
    ' CORRECCION DE EJES
    '
    ' El grupo H de CATIA es el vertical fisico.
    '
    ' El grupo V de CATIA es el horizontal fisico
    ' pero con sentido contrario.
    ' ========================================================

    gQV = CDbl(gValores(CMD_H1 - 1))

    gQH = -CDbl(gValores(CMD_V1 - 1))


    ' --------------------------------------------------------
    ' Abrir interfaz
    ' --------------------------------------------------------

    frmLengua.ActualizarPantalla

    frmLengua.Show vbModeless


    Exit Sub


' ============================================================
' ERRORES
' ============================================================

ErrorMecanismo:

    MsgBox _
        "No pude acceder a DMU Kinematics." & vbCrLf & vbCrLf & _
        "Error " & Err.Number & vbCrLf & _
        Err.Description, _
        vbCritical, _
        "Control de lengua"

    Exit Sub


ErrorLectura:

    MsgBox _
        "No pude leer los valores de los Commands." & vbCrLf & vbCrLf & _
        "Error " & Err.Number & vbCrLf & _
        Err.Description, _
        vbCritical, _
        "Control de lengua"

    Exit Sub

End Sub


' ============================================================
' APLICAR MOVIMIENTO
' ============================================================

Public Sub AplicarLengua()

    Dim pasosAlcanzados As Long


    On Error GoTo ErrorSolver


    ' --------------------------------------------------------
    ' Leer los 14 Commands actuales
    ' --------------------------------------------------------

    Call gMechanism.GetCommandValues(gValores)


    ' ========================================================
    ' MOVIMIENTO HORIZONTAL REAL
    '
    ' Nuestro gQH:
    '
    '   positivo = DERECHA
    '   negativo = IZQUIERDA
    '
    ' En tu mecanismo el grupo CMD_V mueve horizontal,
    ' pero esta invertido.
    '
    ' Por eso usamos:
    '
    '       -gQH
    ' ========================================================

    gValores(CMD_V1 - 1) = -CDbl(gQH)
    gValores(CMD_V2 - 1) = -CDbl(gQH)
    gValores(CMD_V3 - 1) = -CDbl(gQH)
    gValores(CMD_V4 - 1) = -CDbl(gQH)


    ' ========================================================
    ' MOVIMIENTO VERTICAL REAL
    '
    ' Nuestro gQV:
    '
    '   positivo = ARRIBA
    '   negativo = ABAJO
    '
    ' En tu mecanismo el grupo CMD_H es el vertical real.
    ' ========================================================

    gValores(CMD_H1 - 1) = CDbl(gQV)
    gValores(CMD_H2 - 1) = CDbl(gQV)
    gValores(CMD_H3 - 1) = CDbl(gQV)
    gValores(CMD_H4 - 1) = CDbl(gQV)


    ' ========================================================
    ' MOVER MECANISMO
    ' ========================================================

    pasosAlcanzados = 0

    Call gMechanism.PutCommandValuesWithMultiSteps( _
        gValores, _
        5, _
        pasosAlcanzados)


    ' --------------------------------------------------------
    ' Actualizar interfaz
    ' --------------------------------------------------------

    frmLengua.ActualizarPantalla


    Exit Sub


ErrorSolver:

    MsgBox _
        "CATIA no pudo mover el mecanismo." & vbCrLf & vbCrLf & _
        "Error " & Err.Number & vbCrLf & _
        Err.Description, _
        vbCritical, _
        "Control de lengua"

End Sub


' ============================================================
' LIMITAR ANGULO
' ============================================================

Public Function Limitar( _
    ByVal valor As Double, _
    ByVal minimo As Double, _
    ByVal maximo As Double) As Double


    If valor < minimo Then
        valor = minimo
    End If


    If valor > maximo Then
        valor = maximo
    End If


    Limitar = valor

End Function

Attribute VB_Name = "frmLengua"
Attribute VB_Base = "0{B79887AB-DECC-4BB9-B61E-E03A77EB5B0F}{A080FE7F-864B-4963-AD67-581190B5D671}"
Attribute VB_GlobalNameSpace = False
Attribute VB_Creatable = False
Attribute VB_PredeclaredId = True
Attribute VB_Exposed = False
Attribute VB_TemplateDerived = False
Attribute VB_Customizable = False
Option Explicit


' ============================================================
' OBTENER PASO ANGULAR
' ============================================================

Private Function ObtenerPaso() As Double

    Dim texto As String
    Dim valor As Double

    texto = Trim(txtpaso.Text)

    ' Permitir coma decimal
    texto = Replace(texto, ",", ".")

    valor = Val(texto)

    If valor <= 0 Then

        MsgBox _
            "El paso debe ser mayor que cero." & vbCrLf & _
            "Ejemplo: 0.5", _
            vbExclamation, _
            "Paso angular"

        ObtenerPaso = 0

        Exit Function

    End If

    ObtenerPaso = valor

End Function


' ============================================================
' ARRIBA
' ============================================================

Private Sub cmdArriba_Click()

    Dim paso As Double

    paso = ObtenerPaso()

    If paso <= 0 Then Exit Sub

    gQV = Limitar( _
        gQV + paso, _
        -LIMITE_V, _
        LIMITE_V)

    AplicarLengua

End Sub


' ============================================================
' ABAJO
' ============================================================

Private Sub cmdAbajo_Click()

    Dim paso As Double

    paso = ObtenerPaso()

    If paso <= 0 Then Exit Sub

    gQV = Limitar( _
        gQV - paso, _
        -LIMITE_V, _
        LIMITE_V)

    AplicarLengua

End Sub


' ============================================================
' IZQUIERDA
' ============================================================

Private Sub cmdIzquierda_Click()

    Dim paso As Double

    paso = ObtenerPaso()

    If paso <= 0 Then Exit Sub

    gQH = Limitar( _
        gQH - paso, _
        -LIMITE_H, _
        LIMITE_H)

    AplicarLengua

End Sub


' ============================================================
' DERECHA
' ============================================================

Private Sub cmdDerecha_Click()

    Dim paso As Double

    paso = ObtenerPaso()

    If paso <= 0 Then Exit Sub

    gQH = Limitar( _
        gQH + paso, _
        -LIMITE_H, _
        LIMITE_H)

    AplicarLengua

End Sub


' ============================================================
' ARRIBA + IZQUIERDA
' ============================================================

Private Sub cmdArribaIzquierda_Click()

    Dim paso As Double

    paso = ObtenerPaso()

    If paso <= 0 Then Exit Sub


    gQV = Limitar( _
        gQV + paso, _
        -LIMITE_V, _
        LIMITE_V)


    gQH = Limitar( _
        gQH - paso, _
        -LIMITE_H, _
        LIMITE_H)


    AplicarLengua

End Sub


' ============================================================
' ARRIBA + DERECHA
' ============================================================

Private Sub cmdArribaDerecha_Click()

    Dim paso As Double

    paso = ObtenerPaso()

    If paso <= 0 Then Exit Sub


    gQV = Limitar( _
        gQV + paso, _
        -LIMITE_V, _
        LIMITE_V)


    gQH = Limitar( _
        gQH + paso, _
        -LIMITE_H, _
        LIMITE_H)


    AplicarLengua

End Sub


' ============================================================
' ABAJO + IZQUIERDA
' ============================================================

Private Sub cmdAbajoIzquierda_Click()

    Dim paso As Double

    paso = ObtenerPaso()

    If paso <= 0 Then Exit Sub


    gQV = Limitar( _
        gQV - paso, _
        -LIMITE_V, _
        LIMITE_V)


    gQH = Limitar( _
        gQH - paso, _
        -LIMITE_H, _
        LIMITE_H)


    AplicarLengua

End Sub


' ============================================================
' ABAJO + DERECHA
' ============================================================

Private Sub cmdAbajoDerecha_Click()

    Dim paso As Double

    paso = ObtenerPaso()

    If paso <= 0 Then Exit Sub


    gQV = Limitar( _
        gQV - paso, _
        -LIMITE_V, _
        LIMITE_V)


    gQH = Limitar( _
        gQH + paso, _
        -LIMITE_H, _
        LIMITE_H)


    AplicarLengua

End Sub


' ============================================================
' CENTRO
' ============================================================

Private Sub cmdCentro_Click()

    gQV = 0#
    gQH = 0#

    AplicarLengua

End Sub


' ============================================================
' ACTUALIZAR PANTALLA
' ============================================================

Public Sub ActualizarPantalla()

    lblVertical.Caption = _
        "Vertical: " & _
        Format(gQV, "0.00") & _
        " deg"


    lblHorizontal.Caption = _
        "Horizontal: " & _
        Format(gQH, "0.00") & _
        " deg"

End Sub
